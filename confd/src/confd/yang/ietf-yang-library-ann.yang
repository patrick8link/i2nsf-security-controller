module ietf-yang-library-ann {
  namespace "urn:dummy";
  prefix dummy;

  import tailf-common {
    prefix tailf;
  }
  import ietf-yang-library {
    prefix yanglib;
  }

  organization "Tail-f Systems";

  description
    "Annotation module for ietf-yang-library.

     Copyright 2019-2023 Cisco Systems, Inc.
     All rights reserved.
     Permission is hereby granted to redistribute this file without
     modification.";

  revision 2023-02-21 {
    description
      "Released as part of ConfD-8.0.3 / NCS-6.0.3.

       Annotate module as an internal data provider with tailf:internal-dp.";
  }

  tailf:annotate "/yanglib:yang-library" {
    tailf:callpoint "yanglib" {
      tailf:internal;
    }
  }
  tailf:annotate "/yanglib:modules-state" {
    tailf:callpoint "yanglib" {
      tailf:internal;
    }
  }

  tailf:annotate-module "ietf-yang-library" {
    tailf:internal-dp;
  }
}
