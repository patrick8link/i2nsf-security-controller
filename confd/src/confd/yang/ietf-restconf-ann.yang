module ietf-restconf-ann {
  namespace "urn:dummy";
  prefix dummy;

  import tailf-common {
    prefix tailf;
  }

  organization "Tail-f Systems";

  description
    "Annotation module for ietf-restconf.

     Copyright 2019 Cisco Systems, Inc.
     All rights reserved.
     Permission is hereby granted to redistribute this file without
     modification";

  tailf:annotate-module 'ietf-restconf' {
    tailf:export rest;
    // we need to export to netconf b/c ietf-subscribed-notifications
    // imports it
    tailf:export netconf;
  }
}
