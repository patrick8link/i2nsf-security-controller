module tailf-restconf-error {
  yang-version 1.1;
  namespace "http://tail-f.com/ns/tailf-restconf-error";
  prefix tfrcerr;

  tailf:export none;

  import tailf-common {
    prefix tailf;
  }

  import ietf-restconf {
    prefix rc;
  }

  description
    "This module uses the errors list from ietf-restconf.yang, so a
     transaction can be used to populate and emit the error payload.

     Copyright 2022-2023 Cisco Systems, Inc.
     All rights reserved.
     Permission is hereby granted to redistribute this file without
     modification.";

  revision 2023-01-17 {
    description
      "Released as part of ConfD-8.0.2 / NCS-6.0.2.

       Initial release.";
  }

  rc:yang-data yang-errors {
    uses rc:errors;
  }
}
