module ietf-netconf-acm-ann {
  namespace "urn:dummy";
  prefix dummy;

  import tailf-common {
    prefix tailf;
  }
  import ietf-netconf-acm {
    prefix nacm;
  }

  organization "Tail-f Systems";

  description
    "Annotation module for ietf-netconf-acm.

     Adds the callpoints necessary for using this module with ConfD.

     Copyright 2019-2023 Cisco Systems, Inc.
     All rights reserved.
     Permission is hereby granted to redistribute this file without
     modification.";

  revision 2023-02-21 {
    description
      "Released as part of ConfD-8.0.3 / NCS-6.0.3.

       Annotate module as an internal data provider with tailf:internal-dp.";
  }

  tailf:annotate-module "ietf-netconf-acm" {
    tailf:internal-dp;
  }

  tailf:annotate "/nacm:nacm" {
    tailf:info "Access control";
    tailf:callpoint "ncagent" {
      tailf:config false;
      tailf:internal;
    }
  }
}
