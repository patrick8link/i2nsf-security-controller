module mtest {
  namespace "http://tail-f.com/ns/example/mtest";
  prefix mtest;

  organization "Tail-f Systems (a Cisco company)";

  contact "info@tail-f.com";

  description
    "YANG datamodel for Validation example
     (C) 2005-2018 Tail-f Systems

     Permission to use this code as a starting point hereby granted
     This is ConfD Sample Code.

     See the README file for more information";

  revision 2019-02-14 {
    description "Normalized YANG identifier names.";
  }

  revision 2018-12-06 {
    description "YANG header information updated";
  }

  revision 2009-05-20 {
    description "Initial revision.";
  }

  container mtest {
    leaf a-number {
      type int64;
      default 42;
    }
    leaf b-number {
      type int64;
      default 7;
    }
  }
}
