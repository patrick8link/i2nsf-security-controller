module arpe-config {
  namespace "http://tail-f.com/ns/example/arpe-config";
  prefix acfg;

  organization "Tail-f Systems (a Cisco company)";

  contact "info@tail-f.com";

  description
    "YANG datamodel for configuration of the push script.
     (C) 2019 Tail-f Systems

     Permission to use this code as a starting point hereby granted
     This is ConfD Sample Code.

     See the README file for more information";

  revision 2019-05-10 {
    description "Initial revision.";
  }

  container arpe-config {
    leaf interval {
      description "Interval for push updates in seconds";
      type uint8;
      default 10;
    }
  }
}
