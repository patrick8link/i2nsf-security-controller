module scli {
  namespace "http://tail-f.com/ns/example/scli";
  prefix scli;

  import ietf-inet-types {
    prefix inet;
  }

  organization "Tail-f Systems (a Cisco company)";

  contact "info@tail-f.com";

  description
    "YANG datamodel for MAAPI for CLI application example
     (C) 2005-2018 Tail-f Systems

     Permission to use this code as a starting point hereby granted
     This is ConfD Sample Code.

     See the README file for more information";

  revision 2018-12-04 {
    description "YANG header information updated";
  }

  revision 2009-09-30 {
    description "Initial revision.";
  }

  container root {
    leaf foo {
      type string;
      default fooo;
    }
    leaf bar {
      type int32;
      default 66;
    }
    container servers {
      list server {
        key name;
        max-elements 64;
        leaf name {
          type string;
        }
        leaf ip {
          type inet:ip-address;
          mandatory true;
        }
        leaf port {
          type inet:port-number;
          mandatory true;
        }
      }
    }
  }
}
