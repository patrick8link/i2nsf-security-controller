module secret_model {
  namespace "urn:example:secret_model";
  prefix esm;

  container secret_model {
    list secrets {
      key id;

      leaf id {
        type int32;
      }

      leaf address {
        type string;
      }
    }
  }
}
