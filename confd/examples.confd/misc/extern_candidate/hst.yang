module hst {
  namespace "http://tail-f.com/ns/example/hst";
  prefix hst;

  import ietf-inet-types {
    prefix inet;
  }
  import tailf-common {
    prefix tailf;
  }

  organization "Tail-f Systems (a Cisco company)";

  contact "info@tail-f.com";

  description
    "YANG datamodel for External candidate example
     (C) 2005-2018 Tail-f Systems

     Permission to use this code as a starting point hereby granted
     This is ConfD Sample Code.

     See the README file for more information";

  revision 2018-12-04 {
    description "YANG header information updated";
  }

  revision 2009-05-25 {
    description "Initial revision.";
  }

  /* A set of host structures  */
  container hosts {
    tailf:callpoint hcp;

    list host {
      key name;
      max-elements 64;
      leaf name {
        type string;
      }
      leaf domain {
        type string;
        mandatory true;
      }
      leaf defgw {
        type inet:ip-address;
        mandatory true;
      }
      /* Write a validation rule to check that the defgw   */
      /* resides on exactly one of the networks defined below  */
      container interfaces {
        tailf:callpoint icp;
        list interface {
          key name;
          max-elements 64;
          leaf name {
            type string;
          }
          leaf ip {
            type inet:ip-address;
            mandatory true;
          }
          leaf mask {
            type inet:ip-address;
            mandatory true;
          }
          leaf enabled {
            type boolean;
            mandatory true;
          }
        }
      }
    }
  }
}
