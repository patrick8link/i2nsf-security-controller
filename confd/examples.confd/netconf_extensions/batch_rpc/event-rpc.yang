module event-rpc {
  namespace "http://example.com/event";
  prefix ev;

  import tailf-common {
    prefix tailf;
  }

  organization "Tail-f Systems (a Cisco company)";

  contact "info@tail-f.com";

  description
    "YANG datamodel for NETCONF batch RPC example
     (C) 2005-2018 Tail-f Systems

     Permission to use this code as a starting point hereby granted
     This is ConfD Sample Code.

     See the README file for more information";

  revision 2018-12-04 {
    description "YANG header information updated";
  }

  revision 2009-06-15 {
    description "Initial revision.";
  }

  rpc subscribe {
    tailf:exec "./event" {
      tailf:wd ".";
      tailf:raw-xml {
        tailf:batch;
      }
    }
  }
}
