module types {
  namespace "http://tail-f.com/ns/example/types";
  prefix types;


  import tailf-common {
    prefix tailf;
  }

  import ietf-inet-types {
    prefix inet;
  }

  organization "Tail-f Systems (a Cisco company)";

  contact "info@tail-f.com";

  description
    "YANG datamodel for User defined types in Erlang example
     (C) 2005-2018 Tail-f Systems

     Permission to use this code as a starting point hereby granted
     This is ConfD Sample Code.

     See the README file for more information";

  revision 2019-02-14 {
    description "Normalized YANG identifier names.";
  }

  revision 2018-11-30 {
    description "YANG header information updated";
  }

  revision 2013-02-05 {
    description "Initial revision.";
  }

  typedef port-type {
    type string;
    tailf:info "shelf/slot/port";
    tailf:typepoint port-type;
  }
  container system {
    list port {
      key name;
      leaf name {
        type port-type;
      }
      leaf ip {
        type inet:ip-address;
      }
    }
    leaf mgmt-port {
      type port-type;
      default "0/0/0";
    }
  }
}
