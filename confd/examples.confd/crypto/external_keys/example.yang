module example {
  namespace "http://tail-f.com/ns/example";
  prefix ex;

  import tailf-common {
    prefix tailf;
  }

  container strings {
    list string {
      key id;

      leaf id {
        type int32;
      }

      leaf secret {
        type tailf:aes-cfb-128-encrypted-string;
        mandatory true;
      }
    }
  }
}
