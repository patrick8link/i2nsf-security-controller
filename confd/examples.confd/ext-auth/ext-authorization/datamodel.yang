module datamodel {
    namespace "http://tail-f.com/ns/example/datamodel";
    prefix datamodel;

    import tailf-common { prefix tailf; }

    organization "Tail-f Systems (a Cisco company)";

    contact "info@tail-f.com";

    description
      "YANG datamodel for External authorization example
       (C) 2005-2018 Tail-f Systems

       Permission to use this code as a starting point hereby granted
       This is ConfD Sample Code.

       See the README file for more information";

    revision 2019-02-14 {
        description "Normalized YANG identifier names.";
    }

    revision 2018-11-28 {
      description "YANG header information updated";
    }

    revision 2018-06-18 {
      description "Initial revision.";
    }

    grouping grouping-items {
        leaf name {
            type string;
        }
        leaf value {
            type uint32;
        }
    }

    container example-config {
        list items {
            key name;
            uses grouping-items;
        }
    }

    container example-state {
        config false;
        tailf:cdb-oper;
        list items {
            key name;
            uses grouping-items;
        }
    }

}
