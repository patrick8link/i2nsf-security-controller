module ranges-multi {

  namespace "https://tail-f.com/example/ranges-multi";
  prefix "ranges-multi";

  import tailf-common {
    prefix tailf;
  }

  organization "Tail-f Systems (a Cisco company)";

  contact "info@tail-f.com";

  description
    "YANG datamodel for Range callback from multiple applications example
     (C) 2005-2018 Tail-f Systems

     Permission to use this code as a starting point hereby granted
     This is ConfD Sample Code.

     See the README file for more information";

  revision 2018-11-28 {
    description "YANG header information updated";
  }

  revision 2018-06-18 {
    description "Initial revision.";
  }

  container ranges-multi {

    list nodes {
      config false;
      tailf:callpoint enum-callpoint;

      key "node-type node-id";

      leaf node-type {
        type enumeration {
          enum ethernet;
          enum wireless;
          enum optical;
          enum coaxial;
        }
      }

      leaf node-id {
        type uint32;
      }

      leaf payload {
        type string;
        description "Dummy payload leaf to show callback invocations";
      }
    }
  }
}
