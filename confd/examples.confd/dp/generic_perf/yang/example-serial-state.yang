module example-serial-state {
  namespace "http://tail-f.com/ns/example/serial-state";
  prefix ex-state;

  import router-state {
    prefix r-state;
  }

  import ietf-yang-types {
    prefix yang;
  }

  import ietf-inet-types {
    prefix inet;
  }

  organization "Tail-f Systems (a Cisco company";

  contact "info@tail-f.com";

  description
    "An example module describing a serial interface component that
      augment a parent interface component.
    (C) 2005-2020 Tail-f Systems

  Permission to use this code as a starting point hereby granted
  This is ConfD Sample Code.

  See the README file for more information
  ";

  revision 2020-02-27 {
    description
      "Initial revision.";
  }

  augment /r-state:sys/r-state:interfaces {
    list serial {
      key name;
      leaf name {
        type string;
      }

      container ppp {
        leaf accounting {
          type string;
        }
      }

      container authentication {
        leaf method {
          type enumeration {
            enum chap;
            enum eap;
            enum ms-chap;
            enum ms-chap-v2;
            enum pap;
          }
        }
        leaf list-name {
          type string;
        }
        leaf one-time {
          type empty;
        }
        leaf optional {
          type empty;
        }
      }

      leaf authorization {
        type string;
      }

      container ipcp {
        container dns {
          leaf primary {
            type inet:ipv4-address;
          }
        }
      }

      container multilink {
        presence true;
        container links {
          container minimum {
            leaf minimum-value {
              type uint8;
            }
            leaf mandatory {
              type empty;
            }
          }
        }
        leaf group {
          type uint32;
        }
        container fragment {
          container delay {
            leaf delay-value {
              type uint16;
            }
            leaf additional-delay-value {
              type uint16;
            }
          }
        }
      }
      container status {
        container receive {
          uses r-state:commonPacketsCounters;
        }
        container transmit {
          uses r-state:txPacketsCounters;
        }
      }
    }
  }
}
