module ports {
  namespace "http://tail-f.com/ns/example/ports";
  prefix ports;

  import tailf-common {
    prefix tailf;
  }

  organization "Tail-f Systems (a Cisco company)";

  contact "info@tail-f.com";

  description
    "YANG datamodel for find_next callback example
     (C) 2005-2018 Tail-f Systems

     Permission to use this code as a starting point hereby granted
     This is ConfD Sample Code.

     See the README file for more information";

  revision 2018-11-28 {
    description "YANG header information updated";
  }

  revision 2012-06-07 {
    description "Initial revision.";
  }

  list port {
    key "slot port";
    config false;
    tailf:callpoint ps;
    tailf:cli-no-key-completion;
    leaf slot {
      type int8;
    }
    leaf port {
      type int8;
    }
    leaf status {
      type enumeration {
        enum "disabled";
        enum "active";
        enum "error";
      }
      mandatory true;
    }
  }
}
