module routes {
  namespace "http://tail-f.com/ns/example/routes/1.0";
  prefix r;

  import tailf-common {
    prefix tailf;
  }

  organization "Tail-f Systems (a Cisco company)";

  contact "info@tail-f.com";

  description
    "YANG datamodel for Delayed Reply Data Provider example
     (C) 2005-2018 Tail-f Systems

     Permission to use this code as a starting point hereby granted
     This is ConfD Sample Code.

     See the README file for more information";

  revision 2018-11-28 {
    description "YANG header information updated";
  }

  revision 2017-11-17 {
    description "Initial revision.";
  }

  container routes {
    tailf:callpoint "routescp";
    list route {
      key "id";
      leaf id {
        type int32 {
          range "0..99";
        }
      }
      leaf value {
        type int32;
      }
    }
  }
}
