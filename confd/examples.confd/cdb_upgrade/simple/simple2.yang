/* Copyright 2005-2009 Tail-f Systems AB */
module simple2 {
  namespace "http://tail-f.com/ns/example/simple";
  prefix simple;

 organization "Tail-f Systems (a Cisco company)";

  contact "info@tail-f.com";

  description
    "YANG datamodel for Simple CDB upgrade example
     (C) 2005-2018 Tail-f Systems

     Permission to use this code as a starting point hereby granted
     This is ConfD Sample Code.

     See the README file for more information";

  revision 2019-02-14 {
    description "Normalized YANG identifier names.";
  }

  revision 2018-11-28 {
    description "YANG header information updated";
  }

  revision 2009-09-01 {
    description "Updated version.";
  }
  revision 2009-04-01 {
    description "Initial revision.";
  }

  typedef my-type2 {
    type int32 {
      range "0 .. 50000";
    }
  }
  typedef color-type {
    type enumeration {
      enum none;
      enum blue;
      enum yellow;
      enum red;
      enum green;
      enum white;
      enum black;
      enum purple;
      enum pink;
    }
  }
  container simple {
    leaf color {
      type color-type;
      default none;
    }
    leaf value1 {
      type int32;
      mandatory true;
    }
    leaf value2 {
      type my-type2;
      mandatory true;
    }
    leaf value3 {
      type int32;
      mandatory true;
    }
/*  value4 and value5 deleted  */
/*  new element  */
    container foo {
      leaf bar {
        type int32;
        default 42;
      }
    }
    leaf value6 {
      type uint16;
      default 12345;
    }
/*  no longer optional  */
    leaf value7 {
      type int32;
      default 7;
    }
    leaf value8 {
      type int32;
      default 8;
    }
  }
}
