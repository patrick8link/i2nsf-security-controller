module simple {
  namespace "http://tail-f.com/ns/example/simple";
  prefix simple;

  import tailf-common {
    prefix tailf;
  }

  organization "Tail-f Systems (a Cisco company)";

  contact "info@tail-f.com";

  description
    "YANG datamodel for In-service Upgrade example
     (C) 2005-2018 Tail-f Systems

     Permission to use this code as a starting point hereby granted
     This is ConfD Sample Code.

     See the README file for more information";

  revision 2019-02-14 {
    description "Normalized YANG identifier names.";
  }

  revision 2018-11-28 {
    description "YANG header information updated";
  }

  revision 2009-04-01 {
    description "Initial revision.";
  }

  typedef my-type1 {
    type int32 {
      range "0 .. 7";
    }
  }

  typedef ipv4-address-mask {
    type string;
    tailf:info "IPv4-address/mask-length";
    tailf:typepoint ipv4-mask;
  }

  container simple {
    leaf color {
      type string;
      mandatory true;
    }
    leaf ip {
      type ipv4-address-mask;
    }
    leaf value1 {
      type my-type1;
      mandatory true;
    }
    leaf value2 {
      type int16;
      mandatory true;
    }
    leaf value3 {
      type int32;
      mandatory true;
    }
    leaf value4 {
      type int64;
      default 31415926;
    }
    leaf value5 {
      type uint8;
      default 42;
    }
    leaf value6 {
      type int16;
      mandatory true;
    }
    leaf value7 {
      type int32;
    }
    leaf value8 {
      type int8;
    }
    container p {
      presence true;
    }
  }
  container stats {
    config false;
    tailf:cdb-oper {
      tailf:persistent true;
    }
    leaf version {
      type string;
    }
    leaf hardware {
      type string;
    }
    leaf revision {
      type string;
    }
  }
}
