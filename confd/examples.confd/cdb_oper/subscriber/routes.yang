module routes {

  namespace "http://tail-f.com/ns/example/routes";
  prefix routes;

  import ietf-inet-types {
    prefix inet;
  }

  import tailf-common {
    prefix tailf;
  }

  organization "Tail-f Systems (a Cisco company)";

  contact "info@tail-f.com";

  description
    "YANG datamodel for Subscribing to CDB stored operational data changes
     example
     (C) 2005-2018 Tail-f Systems

     Permission to use this code as a starting point hereby granted
     This is ConfD Sample Code.

     See the README file for more information";

  revision 2018-11-28 {
    description "YANG header information updated";
  }

  revision 2018-05-31 {
    description "Initial revision.";
  }

  container system {

    container ip {

      list route {

        config false;
        // write operational data for this part of model into CDB
        tailf:cdb-oper {
          // keep in RAM only, no need to persist on disk
          tailf:persistent false;
        }

        key "destination";

        leaf destination {
         type inet:ip-address;
        }

        leaf gateway {
         type inet:ip-address;
        }

        leaf netmask {
         type inet:ip-address;
        }

        leaf flags {
         type string;
        }

        leaf metric {
         type uint8;
        }

        leaf ifname {
         type string;
        }
      }
    }
  }
}
