module notif {
  yang-version 1.1;
  namespace "http://tail-f.com/ns/example/notif";
  prefix notif;

  container interfaces {
    list interface {
      key ifIndex;
      leaf ifIndex {
        type uint32;
      }
      leaf desc {
        type string;
      }
      notification link-state {
        leaf state {
          type string;
        }
      }
    }
  }
  notification linkUp {
    leaf ifIndex {
      type leafref {
        path "/interfaces/interface/ifIndex";
      }
      mandatory true;
    }
    leaf extraId {
      type string;
    }
    leaf obj {
      type instance-identifier;
    }
    leaf-list refs {
      type instance-identifier;
    }
    list linkProperty {
      max-elements 64;
      leaf newlyAdded {
        type empty;
      }
      leaf flags {
        type uint32;
        default 0;
      }
      list extensions {
        max-elements 64;
        leaf name {
          type uint32;
          mandatory true;
        }
        leaf value {
          type uint32;
          mandatory true;
        }
      }
    }
  }
  notification linkDown {
    leaf ifIndex {
      type leafref {
        path "/interfaces/interface/ifIndex";
      }
      mandatory true;
    }
  }
}
