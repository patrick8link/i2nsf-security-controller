module ietf-i2nsf-registration-interface {
  yang-version 1.1;

  namespace
    "urn:ietf:params:xml:ns:yang:ietf-i2nsf-registration-interface";

  prefix 
    i2nsfri;

  //RFC Ed.: replace occurrences of XXXX with actual RFC number and
  //remove this note

  import ietf-inet-types {
    prefix inet;
    reference "RFC 6991";
  }
  
  import ietf-i2nsf-capability {
    prefix i2nsfcap;
  // RFC Ed.: replace YYYY with actual RFC number of
  // draft-ietf-i2nsf-capability-data-model and remove this note.
    reference "RFC YYYY: I2NSF Capability YANG Data Model";
  }

  organization
   "IETF I2NSF (Interface to Network Security Functions)
    Working Group";

  contact
    "WG Web: <https://datatracker.ietf.org/wg/i2nsf>
     WG List: <mailto:i2nsf@ietf.org>

     Editor: Sangwon Hyun
     <mailto:shyun@mju.ac.kr>
 
     Editor: Jaehoon Paul Jeong
     <mailto:pauljeong@skku.edu>";

  description
    "This module defines a YANG data model for I2NSF 
     Registration Interface.
     
     The key words 'MUST', 'MUST NOT', 'REQUIRED', 'SHALL',
     'SHALL NOT', 'SHOULD', 'SHOULD NOT', 'RECOMMENDED',
     'NOT RECOMMENDED', 'MAY', and 'OPTIONAL' in this
     document are to be interpreted as described in BCP 14
     (RFC 2119) (RFC 8174) when, and only when, they appear
     in all capitals, as shown here.

     Copyright (c) 2023 IETF Trust and the persons
     identified as authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision "2023-04-17" {
    description "Initial revision";
    reference
      "RFC XXXX: I2NSF Registration Interface YANG Data Model";
    // RFC Ed.: replace XXXX with actual RFC number and remove
    // this note     
  }

  grouping nsf-specification {
    description
      "Description of the specification of an NSF.";
      
    leaf packet-processing {
      type uint64;
      units "pps";
      description
        "The overall packet processing capability of the NSF measured in
         packets per second (pps).";
    }
      
    container bandwidth {
      description
        "Network bandwidth available on an NSF
         in the unit of Bps (Bytes per second).";
  
      leaf outbound {
        type uint64;
        units "Bps";
        description
          "The maximum aggregate outbound network bandwidth across all
           interfaces available to the NSF in bytes per second (Bps).";
      }
      
      leaf inbound {
        type uint64;
        units "Bps";
        description
          "The maximum aggregate inbound network bandwidth across all
           interfaces available to the NSF in bytes per second (Bps).";          
      }
    }
    
  }
 
  grouping nsf-access-info {
    description
      "Information required to access an NSF.";
    leaf ip {
      type inet:ip-address-no-zone;
      description
        "Either an IPv4 or IPv6 address of this NSF.";
    }
    leaf port {
      type inet:port-number;
      description
        "Port available on this NSF";
    }
    leaf management-protocol {
      type enumeration {
        enum NETCONF {
          description
            "Represents the management protocol NETCONF.";
          reference
            "RFC 6241: Network Configuration Protocol (NETCONF)";
        }
        enum RESTCONF {
          description
            "Represents the management protocol RESTCONF.";
          reference
            "RFC 8040: RESTCONF Protocol";
        }
      } 
      description
        "The management protocol used to manage the NSF.";
    }
  }
  
  grouping nsf {
    description
      "The information of an NSF. It consists of the name of the NSF,
       NSF capabilities, NSF specifications, and NSF access 
       information";
    leaf nsf-name {
      type string;
      description
        "The name of this registered NSF. The NSF name MUST be 
         unique to identify the NSF with the capability. The name
         can be an arbitrary string including Fully Qualified
         Domain Name (FQDN).";
    }
    leaf version {
      type string;
      description
        "The NSF's current version level of the software in use. 
         This string MAY indicate the specific software build date and
         target variant information.";
    }
    uses i2nsfcap:nsf-capabilities;
    container nsf-specification {
      description
        "The specification of an NSF.";
      uses nsf-specification;
    }
    container nsf-access-info {
      description
        "Network access information of this NSF.";
      uses nsf-access-info;
    }
  }
   
  rpc nsf-capability-registration {
    description
      "Description of the capabilities that the
       Security Controller requests to the DMS";
    input {
      container query-nsf-capability {
        description
          "The query used to request NSFs. The specified
           capabilities in this field restrict the output field.";
        uses i2nsfcap:nsf-capabilities;
        reference "RFC YYYY: I2NSF Capability YANG Data Model";
      //RFC Ed.: replace YYYY with actual RFC number of
      //draft-ietf-i2nsf-capability-data-model and remove this note.
      }
    }
    output {
      list nsf {
        key "nsf-name";
        description
          "The reply of the query to register the NSFs capabilities.
           The capabilities requested in the input field can be covered
           by multiple NSFs. This list consists of NSF(s) that cover
           every capability specified in the input field.  The
           selection method of which NSF(s) that should be listed in
           the output field depends on the implementer.  If any of
           the capabilities specified in the input field cannot be
           covered by any NSF, the reply should return an <rpc-error>
           with <error-message> of those capabilities.";
        uses nsf;
      }
    }
  }
  
  notification nsf-capability-update {
    description
      "This notification is sent when there are updates on the
       capabilities of one or more NSFs. The list of NSFs provided in 
       this notification includes the current capabilities of each NSF.
       Note that the returned capabilities represent the full 
       capabilities of each NSF.";
    list nsf {
      key "nsf-name";
      description
        "List of NSFs with capabilities updated. The returned 
         capabilities are the current capabilities of the NSF.";
      uses nsf;
    }
  }
}
